;=========================================================================
; Command: DWOO
;-------------------------------------------------------------------------
; Summary: Toggle Diewts layer On/Off
;-------------------------------------------------------------------------

(defun c:dwo (/ lay)
  (if (tblsearch "layer" "Diewts")
    (progn
      (setq lay (entget (tblobjname "layer" "Diewts"))
      lay (subst (cons 62 (- (cdr (assoc 62 lay)))) (assoc 62 lay) lay))
      (entmod lay)
      (entupd (cdr (assoc -1 lay)))
      )
    )
(princ)
)
;=========================================================================

;-END FILE

;=========================================================================
; Command: DWX (Die Weights off)
;-------------------------------------------------------------------------
; Summary: Turns DieWTS Layer off
;-------------------------------------------------------------------------
(defun C:dwx ( / )
	 (command "_.-layer" "off" "DIEWTS" "y" "")

(princ)
)
;=========================================================================

;-END FILE

;=========================================================================
; Command: DWO (Die Weights On)
;-------------------------------------------------------------------------
; Summary: Turns DieWTS Layer On
;-------------------------------------------------------------------------
(defun C:dwo ( / )
	 (command "_.-layer" "on" "DIEWTS" "")

(princ)
)
;=========================================================================

;-END FILE
